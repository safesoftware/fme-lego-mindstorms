FME workspace RoombaSimulator.fmw

Creator
    GEOMTYPE = 2D Coordinate List
    NUM = 1
    COORDS = 0 0
    CREATED -> AttributeCreator
AttributeCreator
    ATTR_LIST = _num_moves,0,_num_spins,0,_slope_x,1,_slope_y,0,_rotation_angle,0
    -> RoombaSimulator
RoombaSimulator
    MAX_PROXIMITY_BEFORE_TURN = 20
    _SLOPE_X = @Value(_slope_x)
    MAX_MOVES = 7
    _SLOPE_Y = @Value(_slope_y)
    _NUM_MOVES = @Value(_num_moves)
    _ROTATION_ANGLE = @Value(_rotation_angle)
    RATIO_DEGRESS_OF_MOTOR_ROTATION_TO_SPIN = 6.05
    _NUM_SPINS = @Value(_num_spins)
    -> Logger
Logger
    MAXCOORDS = 20
    MESSAGE = Feature is:
    MAXFEATS = 20
    LOGGED -> Inspector
Inspector

FME custom transformer RoombaSimulator

Parameters:
- MAX_PROXIMITY_BEFORE_TURN = 30   # Maximum Proximity Before Turning
- _NUM_MOVES = @Value(_num_moves)   # Num Moves
- MAX_MOVES = 20   # Maximum Number of Moves
- _SLOPE_X = @Value(_slope_x)   # Slope X
- _SLOPE_Y = @Value(_slope_y)   # Slope Y
- _ROTATION_ANGLE = @Value(_rotation_angle)   # Rotation Angle
- RATIO_DEGRESS_OF_MOTOR_ROTATION_TO_SPIN = 6.67   # Ratio between degress of motor rotation and spin
- _NUM_SPINS = @Value(_num_spins)   # Num Spins

LegoMindstormsMover_Input (input)
    -> LegoMindstormsPropertyExtractor
LegoMindstormsPropertyExtractor
    MOTORD_RESET_TACHO = No
    MOTORB_RESET_TACHO = No
    SENSOR3_PROXIMITY_ATTR = _proximity
    MOTORC_RESET_TACHO = No
    SENSOR3_TYPE = IR
    MOTORA_RESET_TACHO = No
    -> TestFilter
TestFilter
    TEST_LIST = BOOL_OP,OR,COMPOSITE_TEST,<Unused>,TEST_CLAUSE,"TEST @Value(_num_moves) >= $(MAX_MOVES)",ReachedMaxMoves,BOOL_OP,OR,COMPOSITE_TEST,<Unused>,TEST_CLAUSE,"TEST @Value(_proximity) <= $(MAX_PROXIMITY_BEFORE_TURN)",CloseToWall
    DEFAULT_VALUE = Move
    ReachedMaxMoves -> Output (output)
    CloseToWall -> AttributeCreator_2
    Move -> LegoMindstormsVehicleMover_2
LegoMindstormsMover_Input (output)

Bookmark: Finished
Note: We've reached the maximum distance we want / to travel. We're done.
Output (output)

Bookmark: Spin
Note: We're too close to a wall to continue moving. / Spin in a random direction and try again.
AttributeCreator_2
    ATTR_LIST = _amount_to_rotate,@Evaluate(@rand()*360)
    -> AttributeCreator_3
AttributeCreator_3
    ATTR_LIST = _rotation_angle,@Evaluate(@Value(_rotation_angle) + @Value(_amount_to_rotate)),_rotation_angle,@Evaluate(@Value(_rotation_angle) - @int(@Value(_rotation_angle) / 360) * 360),_slope_x,@Evaluate(@cos(@degToRad(@Value(_rotation_angle)))),_slope_y,@sin(@degToRad(@Value(_rotation_angle))),_num_spins,@Evaluate(@Value(_num_spins)+1),_direction,"FME_CONDITIONAL:DEFAULT_VALUE'LEFT'BOOL_OP;OR;COMPOSITE_TEST;<Unused>;TEST @Value(_amount_to_rotate) > 180'RIGHT'FME_NUM_CONDITIONS2___",_amount_to_rotate,"FME_CONDITIONAL:DEFAULT_VALUE'_FME_NO_OP_'BOOL_OP;OR;COMPOSITE_TEST;<Unused>;TEST @Value(_amount_to_rotate) > 180'@Evaluate(360-@Value(_amount_to_rotate))'FME_NUM_CONDITIONS2___"
    -> AttributeCreator_7
AttributeCreator_7
    ATTR_LIST = operation,SPIN @Value(_direction) @Value(_amount_to_rotate)
    -> LegoMindstormsVehicleMover
LegoMindstormsVehicleMover
    SPEED = 50
    DURATION_TYPE = ROTATIONS
    RIGHT_MOTOR = B
    LEFT_MOTOR = C
    REVERSE_RIGHT = No
    MOVEMENT_TYPE = SPIN
    DEGREES_OF_ROTATION = @Value(_amount_to_rotate)*$(RATIO_DEGRESS_OF_MOTOR_ROTATION_TO_SPIN)
    REVERSE_LEFT = No
    DIRECTION = @Value(_direction)
    -> AttributeCreator_4

Bookmark: Move Forward!
Note: As far as we can tell, everything is a-ok. / Keep on moving.
LegoMindstormsVehicleMover_2
    SPEED = 50
    DURATION_TYPE = TIME
    RIGHT_MOTOR = B
    LEFT_MOTOR = C
    REVERSE_RIGHT = No
    MOVEMENT_TYPE = STRAIGHT
    REVERSE_LEFT = No
    TIME = 1
    -> AttributeCreator
AttributeCreator
    ATTR_LIST = _num_moves,@Evaluate(@Value(_num_moves)+1),operation,MOVE
    -> CoordinateExtractor

Bookmark: Add new point
CoordinateExtractor
    IND = -1
    Y_ATTR = _y
    Z_DEFAULT = -9999
    X_ATTR = _x
    -> VertexCreator
VertexCreator
    MODE_NAME = Add Point
    YVAL = @Value(_y)+@Value(_slope_y)
    XVAL = @Value(_x)+@Value(_slope_x)
    -> AttributeCreator_4

Bookmark: Update list of operations
AttributeCreator_4
    ATTR_LIST = _operation_index,@Evaluate(@Value(_num_moves)+@Value(_num_spins)-1)
    -> AttributeCreator_5
AttributeCreator_5
    ATTR_LIST = _operation_attr_name,_operations{@Value(_operation_index)}
    -> AttributeCreator_6
AttributeCreator_6
    ATTR_LIST = @Value(_operation_attr_name),@Value(operation)
    -> LegoMindstormsMover_Input (output)
